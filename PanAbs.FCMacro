# Generador de absorbentes de ultrasonido para FreeCAD
# Copyright (C) 2017 
#
# This library is free software; you can redistribute it and/or
# modify it under the terms of the GNU Lesser General Public
# License as published by the Free Software Foundation; either
# version 2.1 of the License, or (at your option) any later version.
#
# This library is distributed in the hope that it will be useful,
# but WITHOUT ANY WARRANTY; without even the implied warranty of
# MERCHANTABILITY or FITNESS FOR A PARTICULAR PURPOSE.  See the GNU
# Lesser General Public License for more details.
#

# importar librerias librerias
import Draft
from PySide import QtGui

# path del .ui
path_to_ui = "C:\Users\Maxi\Google Drive\Aprender\FreeCAD\Macros\GUI\PanAbs.ui"

# limpiar la vista de informe
mw=Gui.getMainWindow()
r=mw.findChild(QtGui.QTextEdit, "Report view")
r.clear()

class TaskPanel:
	def __init__(self):
		# this will create a Qt widget from our ui file
		self.ui = FreeCADGui.PySideUic.loadUi(path_to_ui)
		self.initUI()

	def initUI(self):
		
		# modificacion de btn_crear
		self.ui.btn_crear.clicked.connect(self.onCrear)

		# now make the window visible
		self.ui.show()

	def onCrear(self):
		doc = FreeCAD.newDocument("Absorbente")
		
		# Parametros de entrada
		rep1 = int(self.ui.Edit_CantCu1.text())
		rep2 = int(self.ui.Edit_CantCu2.text())
		base = float(self.ui.Edit_BaseCu.text())
		alto = float(self.ui.Edit_AltCu.text())
		base2 = float(self.ui.Edit_AltBas.text())
		
		cuna = doc.addObject("Part::Wedge","cuna")
		cuna.Xmin = 0.00
		cuna.Ymin = 0.00
		cuna.Zmin = 0.00
		cuna.X2min = base/2
		cuna.Z2min = base/2
		cuna.Xmax = base
		cuna.Ymax = alto
		cuna.Zmax = base
		cuna.X2max = base/2
		cuna.Z2max = base/2
		
		cantidad_i = list(range(rep1))
		cantidad_j = list(range(rep2))
		
		# bucle para clonar 
		for i in cantidad_i:
			for j in cantidad_j: 
				Draft.clone(cuna,App.Vector(base*i,0,base*j)) 
		
		box = doc.addObject("Part::Box","box")
		box.Length = base*rep1
		box.Height = base*rep2
		box.Width = base2
		box.Placement=App.Placement(App.Vector(0,-base2,0), App.Rotation(App.Vector(0,0,1),0), App.Vector(0,0,0)) 

		doc.recompute() 

		self.ui.close()
		
		# informe
		print "---- Datos del modelo ----"
		print "Base             ---> " + self.ui.Edit_BaseCu.text()
		print "Altura           ---> " + self.ui.Edit_AltCu.text()
		print "Cant. elementos  ---> " + self.ui.Edit_CantCu1.text() + " x " + self.ui.Edit_CantCu2.text()
		print "Altura de base   ---> " + self.ui.Edit_AltBas.text()
		print "--------------------------"

# definicion de la clase
form = TaskPanel()
